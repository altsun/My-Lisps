;;;************��N - HI��N BLOCK*************************
(defun Dxf (Id Obj) (cdr (assoc Id (entget Obj))))
(defun an (SSet / Count_an Elem)
 (cond
((/= SSet nil)
(repeat (setq Count_an (sslength SSet))
  	(setq Count_an (1- Count_an)
 	Elem (ssname SSet Count_an))
  	(if (/= 4 (logand 4 (Dxf 70 (tblobjname "layer" (Dxf 8 Elem)))))
 (if (Dxf 60 Elem)
(entmod (subst '(60 . 1) (assoc 60 (entget Elem)) (entget Elem)))
(entmod (append (entget Elem) (list '(60 . 1))))
 )
 (prompt "\nLayer trong Block da bi khoa, khong the hien thi doi tuong nay!")
  	)
)
)  
 )
 (princ)
)
(defun C:B1 (/ ena_an ss )
(while
 (and (setq ena_an (car (entsel "\nChon Block can an:"))) (= (dxf 0 ena_an) "INSERT"))
 (setq ss (ssget "X" (list (cons 2 (dxf 2 ena_an)))))
 (an ss)
)
(princ)
)
(defun c:B2 (/ SSet WhatNext Count_an Elem)
(cond
 ((setq SSet (ssget "_X" '((60 . 1) (0 . "INSERT"))))
  (setq WhatNext "Yes")
  (cond
  ((= WhatNext "Yes")
(prompt "\nVui long doi...!")
(repeat (setq Count_an (sslength SSet))
  	(setq Count_an (1- Count_an)
 	Elem (ssname SSet Count_an))
  	(if (/= 4 (logand 4 (Dxf 70 (tblobjname "layer" (Dxf 8 Elem)))))
 (entmod (subst '(60 . 0) '(60 . 1) (entget Elem)))
 (prompt "\nLayer trong Block da bi khoa, khong the hien thi doi tuong nay!")
  	)
)
(prompt "\nXong...")
)
  )
 )
 (T (prompt "\nKhong co Block nao bi an!"))
)
)
(defun C:B3 (/ ss ssa ss_an index)
(while (not (and
(setq ena_an (car (entsel "\nChon doi tuong Block chi hien thi:")))
(=(dxf 0 ena_an) "INSERT")
))
 (princ " Phai chon mot Block!")
)
(setq ss (ssget "X" (list (cons 2 (dxf 2 ena_an)))) index 0)
(setq ssa (ssget "X" (list (cons 0 "INSERT"))))
(repeat (sslength ss)
 (setq ssa (ssdel (ssname ss index) ssa))
 (setq index (1+ index))
)
(an ssa)
)
