(defun C:HAA (/ ss ent obj i)
 (vl-load-com)
 (if (not *tl*) (setq *tl* 1.0))
 (initget 6)
 (setq tl (getreal (strcat "\nHe so Scale <" (rtos *tl* 2) ">: ")))
 (if (not tl) (setq tl *tl*) (setq *tl* tl))
 (princ "\nChon cac Block can Scale...")
 (setq ss (ssget '((0 . "INSERT"))) i -1)
 (while (< (setq i (1+ i)) (sslength ss))
  (setq ent (ssname ss i))
(if (/= tl 1)
(command "scale" ent "" "non" (cdr (assoc 10 (entget ent))) tl))))
