;;;;;;;;;;;;;;;;;;;;=========================================
(defun Rad_to_Do(radian / Do)
   (setq Do (/ (* radian 180) pi))
)
;;;;;;;;;;;;;;;;;;;;===========================================
(defun R2DPG (gocR / DPG Toando Do Phut1 Phut Giay DPG)
  (setq DPG (list))
  (setq Toando (Rad_to_Do gocR))
  (setq Do (fix Toando))
  (setq Phut1  (* (- Toando Do) 60))
  (setq Phut (fix Phut1))
  (setq Giay   (atof (rtos (* (- phut1 phut) 60) 2 3)))
  (setq DPG (list Do  Phut giay))
  DPG
)
;;;;;;;;;;;;;;;;;;;;===========================================

(defun Atan2 (dx dy / gocAtan b)
  (setq gocAtan (list))
  (cond
    ((and (= dx 0) (> dy 0) )
      (setq gocAtan (/ pi 2))
    )
    ((and (= dx 0) (< dy 0) )
      (setq gocAtan (/ (* 3 pi) 2))
    )
    ((and  (< dx 0) (= dy 0) )
      (setq gocAtan pi)
    )
    ((and  (> dx 0) (= dy 0) )
      (setq gocAtan 0)
    )
    ((and  (= dx 0) (= dy 0) )
      (setq gocAtan 0)
    )
    ((/= dx 0)
     (progn
	(setq b (atan (/ dy dx)))
	(cond
	    ((and (> dx 0) (>= dy 0))
		  (setq gocAtan b)
	    )
	    ((and (< dx 0) (> dy 0))
		  (setq gocAtan (+ pi b))
	    )
	    ((and (< dx 0) (< dy 0))
		  (setq gocAtan (+ pi b))
	    )
	    ((and (> dx 0) (< dy 0))
	          (setq gocAtan (+ (* pi 2) b))
	    )
	)
      )
    )  
  )
  gocAtan
)

;;;;;;;;;;;;;;;;;;;;===========================================
(defun c:TBSMB ( / chon)
  (setq chon (getstring "\nCh\U+1ECDn d\U+1EA1ng l\U+01B0\U+1EDBi b\U+00ECnh sai ( 11 - Hai \U+0111i\U+1EC3m g\U+1ED1c (1 \U+0111\U+1EA7u - 1 cu\U+1ED1i) / 21 - Ba \U+0111i\U+1EC3m g\U+1ED1c (2 \U+0111\U+1EA7u - 1 cu\U+1ED1i) / 22 - B\U+1ED1n \U+0111i\U+1EC3m g\U+1ED1c  (2 \U+0111\U+1EA7u - 2 cu\U+1ED1i):  "))
  (if chon (setq chon (strcase chon nil)))
  (cond
         ((= chon  "11")
	  (2dgoc_1dau_1cuoi)
	 )
         ((= chon  "21")
	  (3dgoc_2dau_1cuoi)
	 )
	 ((= chon  "22")
	  (4dgoc_2dau_2cuoi)
	 )
	 ((or (/= chon  "11")(/= chon  "21")(/= chon  "22"))
	  (alert "Ch\U+1ECDn sai d\U+1EA1ng l\U+01B0\U+1EDBi b\U+00ECnh sai. Tho\U+00E1t....")
	 )
  )
  (princ)
)
;;;;;;;;;;;;;;;;;;;;===========================================
(defun 2dgoc_1dau_1cuoi( / DC DD DPGIAY DPGIAY1 DPGIAY2 DX12 DX13 DY12 DY13 EN ENTTEXT FH
			   FN GOC12 GOC13 GOC213 I J K KC M N OB P P0 P1 P2 P3 PNTPL PNTPL0
			   PNTPLN PNTTEXT PT0 PT1 SSTEXT TENCT TEXT X0 X1 X2 X3 XC XD Y0 Y1
			   Y2 Y3 YC YD ZC ZD)
(vl-load-com)
(setq en (entsel "\nCh\U+1ECDn pline "))
(alert "Qu\U+00E9t ch\U+1ECDn t\U+00EAn \U+0111i\U+1EC3m: ")
(setq sstext (ssget (list (cons 0 "TEXT")) ))
(setq tenct (getstring T "\nNh\U+1EADp t\U+00EAn l\U+01B0\U+1EDBi: "))
(if en
  (progn
    	(setq fn (getfiled "Export File to Adjustment"  "" "csv" 1))
	(if (/= fn nil)
	        (progn
	          (setq fh (open fn "w")
		        ob (vlax-ename->vla-object (car en))
		         n (vlax-curve-getEndParam ob)
		         i 1
			 j 0
			 k 1
			 dd (vlax-curve-getPointAtParam ob 0)
			 dc (vlax-curve-getPointAtParam ob n)
			 xd (car dd)
			 yd (cadr dd)
			 zd (caddr dd)
			 xc (car dc)
			 yc (cadr dc)
			 zc (caddr dc)
		  )
		  (write-line (strcat tenct) fh)
		  (write-line (strcat ( rtos (- n 1) 2 0) "," ( rtos  n  2 0) "," ( rtos 0 2 0) "," ( rtos (- n 1) 2 0) "," ( rtos 2 2 0) ) fh)
		  (write-line (strcat ( rtos 5 2 0) "," ( rtos 0.2 2 1) "," ( rtos 0.2 2 1) "," ( rtos 0.1 2 1)) fh)
		  (write-line (strcat ( rtos n 2 0) "," ( rtos yd 2 3) "," ( rtos xd 2 3))  fh)
		  (write-line (strcat ( rtos (+ n 1) 2 0) "," ( rtos yc 2 3) "," ( rtos xc 2 3))  fh)
		  (while (< k n)
		    (progn
		      	(setq PntPL (vlax-curve-getPointAtParam ob k))    
		  	(repeat (setq m (sslength sstext))
				(setq enttext (entget (ssname sstext (setq m (1- m)))))
			  	(setq Text (cdr (assoc 1 enttext)))
			  	(setq PntText (cdr (assoc 10 enttext)))
			  	(if (and (= (car PntPL) (car PntText)) (= (cadr PntPL) (cadr PntText)))
				  (write-line Text fh)
				)
			)
		    )
	                (setq k (+ k 1))
	          )
		  (setq PntPL0 (vlax-curve-getPointAtParam ob 0))
		  (setq PntPLn (vlax-curve-getPointAtParam ob n))
		  (progn
			  (repeat (setq m (sslength sstext))
					(setq enttext (entget (ssname sstext (setq m (1- m)))))
				  	(setq Text (cdr (assoc 1 enttext)))
				  	(setq PntText (cdr (assoc 10 enttext)))
			    		(if (and (= (car PntPL0) (car PntText)) (= (cadr PntPL0) (cadr PntText)))
					  (write-line Text fh)
					)
			    		(if (and (= (car PntPLn) (car PntText)) (= (cadr PntPLn) (cadr PntText)))
					  (write-line Text fh)
					)
			    
		          )
		  )
	          (while (< i n)
		      (progn
			(setq p1 (vlax-curve-getPointAtParam ob i)
			      p2 (vlax-curve-getPointAtParam ob (- i 1))
			      p3 (vlax-curve-getPointAtParam ob (+ i 1))
			      x1 (car p1)
			      y1 (cadr p1)
			      x2 (car p2)
			      y2 (cadr p2)
			      x3 (car p3)
			      y3 (cadr p3)
			      dx12 (- x2 x1)
			      dy12 (- y2 y1)
			      dx13 (- x3 x1)
			      dy13 (- y3 y1)
			      goc12 (Atan2 dx12 dy12)
			      goc13 (Atan2 dx13 dy13)
			      DPGiay1 (R2DPG  goc12)
			      DPGiay2 (R2DPG  goc13)
			)
			(if (> (car DPGiay1) (car DPGiay2))
			    (setq goc213 (- goc12 goc13))
			    (setq goc213 (+ (* 2 pi) (- goc12 goc13) ))
			)
			(setq DPGiay (R2DPG goc213))
			(if (= (- i 1) 0)
			  (write-line (strcat ( rtos 1 2 0) "," ( rtos n 2 0) "," ( rtos 1 2 0) "," ( rtos 2 2 0) "," ( rtos (car DPGiay) 2 0) "," ( rtos (cadr DPGiay) 2 0) "," ( rtos (caddr DPGiay) 2 3)) fh)
			)
			(if (and (> (- i 1) 0) (< i (- n 1)))
			  (write-line (strcat ( rtos i 2 0) "," ( rtos (- i 1) 2 0) "," ( rtos i 2 0) "," ( rtos ( + i 1) 2 0) "," ( rtos (car DPGiay) 2 0) "," ( rtos (cadr DPGiay) 2 0) "," ( rtos (caddr DPGiay) 2 3)) fh)
		        )
			(if (= (+ i 1) n)
			  (write-line (strcat ( rtos (- n 1) 2 0) "," ( rtos (- n 2) 2 0) "," ( rtos (- n 1) 2 0) "," ( rtos ( + n 1) 2 0) "," ( rtos (car DPGiay) 2 0) "," ( rtos (cadr DPGiay) 2 0) "," ( rtos (caddr DPGiay) 2 3)) fh)
		        )
		      )
		    (setq i (+ i 1))
                  )
		  
		  (while (< j n)
		      (progn
			(setq p (vlax-curve-getPointAtParam ob j)
			      p0 (vlax-curve-getPointAtParam ob (+ j 1))
			      x0 (car p)
			      y0 (cadr p)
			      pt0 (list x0 y0)
			      x1 (car p0)
			      y1 (cadr p0)
			      pt1 (list x1 y1)
			      kc (distance pt0 pt1)
			)
			(if (= j 0)
				(write-line (strcat ( rtos 1 2 0) "," ( rtos n 2 0) "," ( rtos 1 2 0) "," (rtos kc 2 3)) fh)
			)
			(if (and (> j 0) (< j (- n 1)))
				(write-line (strcat ( rtos (+ j 1) 2 0) "," ( rtos j 2 0) "," ( rtos (+ j 1) 2 0) "," (rtos kc 2 3)) fh)
			)
			(if (= j (- n 1))
				(write-line (strcat ( rtos n 2 0) "," ( rtos (- n 1) 2 0) "," ( rtos (+ n 1) 2 0) "," (rtos kc 2 3)) fh)
			)
		      )
	              (setq j (+ j 1))
	         )
		  (close fh)
	         )
        )
   )
)
(princ)
)

;;;;;;;;;;;;;;;;;;;;===========================================

(defun 4dgoc_2dau_2cuoi ( / DC1 DC2 DD1 DD2 DPGIAY DPGIAY1 DPGIAY2 DX12 DX13 DY12 DY13 EN ENTTEXT FH FN GOC12 GOC13 GOC213
			   I J K KC M N OB P P0 P1 P2 P3 PNTPL PNTPL0 PNTPL1 PNTPLN PNTPLN-1 PNTTEXT PT0 PT1 SSTEXT TENCT
			   TEXT X0 X1 X2 X3 XC1 XC2 XD1 XD2 Y0 Y1 Y2 Y3 YC1 YC2 YD1 YD2 ZC1 ZC2 ZD1 ZD2
		        )
(vl-load-com)
(command "undo" "be")
(setq en (entsel "\nCh\U+1ECDn pline "))
(alert "Qu\U+00E9t ch\U+1ECDn t\U+00EAn \U+0111i\U+1EC3m: ")
(setq sstext (ssget (list (cons 0 "TEXT")) ))
(setq tenct (getstring T "\nNh\U+1EADp t\U+00EAn l\U+01B0\U+1EDBi: "))
(if en
  (progn
    	(setq fn (getfiled "Export File to Adjustment APNET _ Yahoo: thanhduan2407"  "" "csv" 1))
	(if (/= fn nil)
	        (progn
	          (setq fh (open fn "w")
		        ob (vlax-ename->vla-object (car en))
		         n (vlax-curve-getEndParam ob)
		         i 1
			 j 1
			 k 2
			 dd1 (vlax-curve-getPointAtParam ob 0)
			 dd2 (vlax-curve-getPointAtParam ob 1)
			 dc1 (vlax-curve-getPointAtParam ob (- n 1))
			 dc2 (vlax-curve-getPointAtParam ob n)
			 xd1 (car dd1)
			 yd1 (cadr dd1)
			 zd1 (caddr dd1)
			
			 xd2 (car dd2)
			 yd2 (cadr dd2)
			 zd2 (caddr dd2)
			
			 xc1 (car dc1)
			 yc1 (cadr dc1)
			 zc1 (caddr dc1)
			
			 xc2 (car dc2)
			 yc2 (cadr dc2)
			 zc2 (caddr dc2)
		  )  
		  (write-line (strcat tenct) fh)
		  (write-line (strcat ( rtos (- n 1) 2 0) "," ( rtos  (- n 2)  2 0) "," ( rtos 0 2 0) "," ( rtos (- n 3) 2 0) "," ( rtos 4 2 0) ) fh)
		  (write-line (strcat ( rtos 5 2 0) "," ( rtos 0.2 2 1) "," ( rtos 0.2 2 1) "," ( rtos 0.1 2 1)) fh)
		  (write-line (strcat ( rtos (- n 2) 2 0) "," ( rtos yd1 2 3) "," ( rtos xd1 2 3)  )  fh)
		  (write-line (strcat ( rtos (- n 1) 2 0) "," ( rtos yd2 2 3) "," ( rtos xd2 2 3)  )  fh)
		  (write-line (strcat ( rtos n 2 0) "," ( rtos yc1 2 3) "," ( rtos xc1 2 3) )  fh)
		  (write-line (strcat ( rtos (+ n 1) 2 0) "," ( rtos yc2 2 3) "," ( rtos xc2 2 3) )  fh)
		  (while (< k ( - n 1))
		    (progn
		      	(setq PntPL (vlax-curve-getPointAtParam ob k))    
		  	(repeat (setq m (sslength sstext))
				(setq enttext (entget (ssname sstext (setq m (1- m)))))
			  	(setq Text (cdr (assoc 1 enttext)))
			  	(setq PntText (cdr (assoc 10 enttext)))
			  	(if (and (= (car PntPL) (car PntText)) (= (cadr PntPL) (cadr PntText)))
				  (write-line Text fh)
				)
			)
		    )
	                (setq k (+ k 1))
	          )
		  (setq PntPL0 (vlax-curve-getPointAtParam ob 0))
		  (setq PntPL1 (vlax-curve-getPointAtParam ob 1))
		  (setq PntPLn-1 (vlax-curve-getPointAtParam ob (- n 1)))
		  (setq PntPLn (vlax-curve-getPointAtParam ob n))
		  (progn
			  (repeat (setq m (sslength sstext))
					(setq enttext (entget (ssname sstext (setq m (1- m)))))
				  	(setq Text (cdr (assoc 1 enttext)))
				  	(setq PntText (cdr (assoc 10 enttext)))
				  	(if (and (= (car PntPL0) (car PntText)) (= (cadr PntPL0) (cadr PntText)))
					  (write-line Text fh)
					  (if (and (= (car PntPL1) (car PntText)) (= (cadr PntPL1) (cadr PntText)))
					  (write-line Text fh)
					    (if (and (= (car PntPLn-1) (car PntText)) (= (cadr PntPLn-1) (cadr PntText)))
					    (write-line Text fh)
					      (if (and (= (car PntPLn) (car PntText)) (= (cadr PntPLn) (cadr PntText)))
					      (write-line Text fh)
					      )
					    )
					  )
					)
			  )

		  )
	          (while (< i n)
		      (progn
			(setq p1 (vlax-curve-getPointAtParam ob i)
			      p2 (vlax-curve-getPointAtParam ob (- i 1))
			      p3 (vlax-curve-getPointAtParam ob (+ i 1))
			      x1 (car p1)
			      y1 (cadr p1)
			      x2 (car p2)
			      y2 (cadr p2)
			      x3 (car p3)
			      y3 (cadr p3)
			      dx12 (- x2 x1)
			      dy12 (- y2 y1)
			      dx13 (- x3 x1)
			      dy13 (- y3 y1)
			      goc12 (Atan2 dx12 dy12)
			      goc13 (Atan2 dx13 dy13)
			      DPGiay1 (R2DPG  goc12)
			      DPGiay2 (R2DPG  goc13)
			)
			(if (> (car DPGiay1) (car DPGiay2))
			    (setq goc213 (- goc12 goc13))
			    (setq goc213 (+ (* 2 pi) (- goc12 goc13) ))
			)
			(setq DPGiay (R2DPG goc213))
			(if (= (- i 1) 0)
			  (write-line (strcat ( rtos 1 2 0) "," ( rtos (- n 2) 2 0) "," ( rtos (- n 1) 2 0) "," ( rtos 1 2 0) "," ( rtos (car DPGiay) 2 0) "," ( rtos (cadr DPGiay) 2 0) "," ( rtos (caddr DPGiay) 2 3)) fh)
			)

			
			(if (= (- i 1) 1)
			  (write-line (strcat ( rtos 2 2 0) "," ( rtos (- n 1) 2 0) "," ( rtos 1 2 0) "," ( rtos 2 2 0) "," ( rtos (car DPGiay) 2 0) "," ( rtos (cadr DPGiay) 2 0) "," ( rtos (caddr DPGiay) 2 3)) fh)
			)


			
			(if (and (> (- i 1) 1) (< i (- n 2)))
			  (write-line (strcat ( rtos i 2 0) "," ( rtos (- i 2) 2 0) "," ( rtos (- i 1) 2 0) "," ( rtos i 2 0) "," ( rtos (car DPGiay) 2 0) "," ( rtos (cadr DPGiay) 2 0) "," ( rtos (caddr DPGiay) 2 3)) fh)
			)

			(if (= i (- n 2))
			  (write-line (strcat ( rtos (- n 2) 2 0) "," ( rtos (- i 2) 2 0) "," ( rtos (- i 1) 2 0) "," ( rtos n 2 0) "," ( rtos (car DPGiay) 2 0) "," ( rtos (cadr DPGiay) 2 0) "," ( rtos (caddr DPGiay) 2 3)) fh)
			)


			(if (= i (- n 1))
			  (write-line (strcat ( rtos (- n 1) 2 0) "," ( rtos (- n 3) 2 0) "," ( rtos n 2 0) "," ( rtos (+ n 1) 2 0) "," ( rtos (car DPGiay) 2 0) "," ( rtos (cadr DPGiay) 2 0) "," ( rtos (caddr DPGiay) 2 3)) fh)
			)
		    )
	            (setq i (+ i 1))
                  )
		  
		  (while (< j n)
		      (progn
			(setq p (vlax-curve-getPointAtParam ob j)
			      p0 (vlax-curve-getPointAtParam ob (+ j 1))
			      x0 (car p)
			      y0 (cadr p)
			      pt0 (list x0 y0)
			      x1 (car p0)
			      y1 (cadr p0)
			      pt1 (list x1 y1)
			      kc (distance pt0 pt1)
			)
			(if (= j 1)
				(write-line (strcat ( rtos 1 2 0) "," ( rtos (- n 1) 2 0) "," ( rtos 1 2 0)  "," (rtos kc 2 3)) fh)
			)
			(if (and (> j 1) (< j (- n 2)))
				(write-line (strcat ( rtos j 2 0) "," ( rtos (- j 1) 2 0) "," ( rtos j 2 0) "," (rtos kc 2 3)) fh)
			)
			(if (= j (- n 2))
				(write-line (strcat ( rtos (- n 2) 2 0) "," ( rtos (- n 3) 2 0) "," ( rtos n 2 0) "," (rtos kc 2 3)) fh)
			)
		      )
	              (setq j (+ j 1))
	         )
	         (close fh)
		  
	         )
        )
   )
)
(princ "\n")
(princ)
)
;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;;
(defun 3dgoc_2dau_1cuoi  ( / DC DD1 DD2 DPGIAY DPGIAY1 DPGIAY2 DX12 DX13 DY12 DY13 EN ENTTEXT FH FN GOC12 GOC13 GOC213
			   I J K KC M N OB P P0 P1 P2 P3 PNTPL PNTPL0 PNTPL1 PNTPLN PNTTEXT PT0 PT1 SSTEXT TENCT TEXT
			   X0 X1 X2 X3 XC XD1 XD2 Y0 Y1 Y2 Y3 YC YD1 YD2 ZC ZD1 ZD2
		         )
(vl-load-com)
(command "undo" "be")
(setq en (entsel "\nCh\U+1ECDn pline "))
(alert "Qu\U+00E9t ch\U+1ECDn t\U+00EAn \U+0111i\U+1EC3m: ")
(setq sstext (ssget (list (cons 0 "TEXT")) ))
(setq tenct (getstring T "\nNh\U+1EADp t\U+00EAn l\U+01B0\U+1EDBi: "))
(if en
  (progn
    	(setq fn (getfiled "Export File to Adjustment APNET _ Yahoo: thanhduan2407"  "" "csv" 1))
	(if (/= fn nil)
	        (progn
	          (setq fh (open fn "w")
		        ob (vlax-ename->vla-object (car en))
		         n (vlax-curve-getEndParam ob)
		         i 1
			 j 1
			 k 2
			 dd1 (vlax-curve-getPointAtParam ob 0)
			 dd2 (vlax-curve-getPointAtParam ob 1)
			 dc (vlax-curve-getPointAtParam ob n)
			 xd1 (car dd1)
			 yd1 (cadr dd1)
			 zd1 (caddr dd1)
			
			 xd2 (car dd2)
			 yd2 (cadr dd2)
			 zd2 (caddr dd2)
			
			 xc (car dc)
			 yc (cadr dc)
			 zc (caddr dc)
			
		  )  
		  (write-line (strcat tenct) fh)
		  (write-line (strcat ( rtos (- n 1) 2 0) "," ( rtos  (- n 1)  2 0) "," ( rtos 0 2 0) "," ( rtos (- n 2) 2 0) "," ( rtos 3 2 0)  ) fh)
		  (write-line (strcat ( rtos 5 2 0) "," ( rtos 0.2 2 1) "," ( rtos 0.2 2 1) "," ( rtos 0.1 2 1)) fh)
		  (write-line (strcat ( rtos (- n 1) 2 0) "," ( rtos yd1 2 3) "," ( rtos xd1 2 3)  )  fh)
		  (write-line (strcat ( rtos n 2 0) "," ( rtos yd2 2 3) "," ( rtos xd2 2 3)  )  fh)
		  (write-line (strcat ( rtos (+ n 1) 2 0) "," ( rtos yc 2 3) "," ( rtos xc 2 3)  )  fh)
		  (while (< k n)
		    (progn
		      	(setq PntPL (vlax-curve-getPointAtParam ob k))
		  	(repeat
			  	(setq m (sslength sstext))
				(setq enttext (entget (ssname sstext (setq m (1- m)))))
			  	(setq Text (cdr (assoc 1 enttext)))
			  	(setq PntText (cdr (assoc 10 enttext)))
			  	(if (and (= (car PntPL) (car PntText)) (= (cadr PntPL) (cadr PntText)))
				  (write-line Text fh)
				)
			)
		    )
	                (setq k (+ k 1))
	          )
		 (progn
			  (setq PntPL0 (vlax-curve-getPointAtParam ob 0))
			  (setq PntPL1 (vlax-curve-getPointAtParam ob 1))
			  (setq PntPLn (vlax-curve-getPointAtParam ob n))
			  (repeat
		    		(setq m (sslength sstext))
				(setq enttext (entget (ssname sstext (setq m (1- m)))))
			  	(setq Text (cdr (assoc 1 enttext)))
			  	(setq PntText (cdr (assoc 10 enttext)))
			  	(if (and (= (car PntPL0) (car PntText)) (= (cadr PntPL0) (cadr PntText)))
				  (write-line Text fh)
				  (if (and (= (car PntPL1) (car PntText)) (= (cadr PntPL1) (cadr PntText)))
				  	(write-line Text fh)
				    	(if (and (= (car PntPLn) (car PntText)) (= (cadr PntPLn) (cadr PntText)))
				        	(write-line Text fh)
				        )
				  )
				)
			   )
		   	   
		            
		  )
	          (while (< i n)
		      (progn
			(setq p1 (vlax-curve-getPointAtParam ob i)
			      p2 (vlax-curve-getPointAtParam ob (- i 1))
			      p3 (vlax-curve-getPointAtParam ob (+ i 1))
			      x1 (car p1)
			      y1 (cadr p1)
			      x2 (car p2)
			      y2 (cadr p2)
			      x3 (car p3)
			      y3 (cadr p3)
			      dx12 (- x2 x1)
			      dy12 (- y2 y1)
			      dx13 (- x3 x1)
			      dy13 (- y3 y1)
			      goc12 (Atan2 dx12 dy12)
			      goc13 (Atan2 dx13 dy13)
			      DPGiay1 (R2DPG  goc12)
			      DPGiay2 (R2DPG  goc13)
			)
			(if (> (car DPGiay1) (car DPGiay2))
			    (setq goc213 (- goc12 goc13))
			    (setq goc213 (+ (* 2 pi) (- goc12 goc13) ))
			)
			(setq DPGiay (R2DPG goc213))
			(if (= (- i 1) 0)
			  (write-line (strcat ( rtos 1 2 0) "," ( rtos (- n 1) 2 0) "," ( rtos n 2 0) "," ( rtos 1 2 0) "," ( rtos (car DPGiay) 2 0) "," ( rtos (cadr DPGiay) 2 0) "," ( rtos (caddr DPGiay) 2 3)) fh)
			)
			
			(if (= (- i 1) 1)
			  (write-line (strcat ( rtos 2 2 0) "," ( rtos n 2 0) "," ( rtos 1 2 0) "," ( rtos 2 2 0) "," ( rtos (car DPGiay) 2 0) "," ( rtos (cadr DPGiay) 2 0) "," ( rtos (caddr DPGiay) 2 3)) fh)
			)
			
			(if (and (> (- i 1) 1) (< i (- n 1)))
			  (write-line (strcat ( rtos i 2 0) "," ( rtos (- i 2) 2 0) "," ( rtos (- i 1) 2 0) "," ( rtos i 2 0) "," ( rtos (car DPGiay) 2 0) "," ( rtos (cadr DPGiay) 2 0) "," ( rtos (caddr DPGiay) 2 3)) fh)
			)

			(if (= i (- n 1))
			  (write-line (strcat ( rtos (- n 1) 2 0) "," ( rtos (- n 3) 2 0) "," ( rtos (- n 2) 2 0) "," ( rtos (+ n 1) 2 0) "," ( rtos (car DPGiay) 2 0) "," ( rtos (cadr DPGiay) 2 0) "," ( rtos (caddr DPGiay) 2 3)) fh)
			)
		    )
	            (setq i (+ i 1))
                  )
		  
		  (while (< j n)
		      (progn
			(setq p (vlax-curve-getPointAtParam ob j)
			      p0 (vlax-curve-getPointAtParam ob (+ j 1))
			      x0 (car p)
			      y0 (cadr p)
			      pt0 (list x0 y0)
			      x1 (car p0)
			      y1 (cadr p0)
			      pt1 (list x1 y1)
			      kc (distance pt0 pt1)
			)
			(if (= j 1)
				(write-line (strcat ( rtos 1 2 0) "," ( rtos n 2 0) "," ( rtos 1 2 0)  "," (rtos kc 2 3)) fh)
			)
			(if (and (> j 1) (< j (- n 1)))
				(write-line (strcat ( rtos j 2 0) "," ( rtos (- j 1) 2 0) "," ( rtos j 2 0) "," (rtos kc 2 3)) fh)
			)
			(if (= j (- n 1))
				(write-line (strcat ( rtos (- n 1) 2 0) "," ( rtos (- n 2) 2 0) "," ( rtos (+ n 1) 2 0) "," (rtos kc 2 3)) fh)
			)
		      )
	              (setq j (+ j 1))
	         )
	         (close fh)
	         )
        )
   )
)
(princ "\n")
(princ)
)

(defun c:daochieu(/ ss count lwp ent obj oname sss revlwpl revln)
  (vl-load-com)
  (defun revlwpl(/ eo el len)
	(setq eo ent)
	(setq el (list(assoc 210 ent)))
	(while (member (assoc 10 ent) ent)
	  (if (= 0.0 (assoc 42 ent))
   (setq el (cons (assoc 42 ent) el))
   (setq el (cons (cons 42 (- (cdr (assoc 42 ent)))) el))
	  )
	  (setq el (cons (assoc 41 ent) el))
	  (setq el (cons (assoc 40 ent) el))
	  (setq el (cons (assoc 10 ent) el))
	  (setq ent (member (assoc 10 ent) ent))
	  (setq ent (cdr ent))
	)
	(setq len(- (LENGTH eo) (LENGTH (member (assoc 10 eo) eo)) 1))
	(while (>= len 0)
	  (setq el (cons (nth len eo) el))
	  (setq len (- len 1))
	)
	(setq ent el)
	(entmod ent)
  )
  (defun revln (/ pt1 pt2)
	(setq pt1 (cons 10 (cdr (assoc 11 ent))))
	(setq pt2 (cons 11 (cdr (assoc 10 ent))))
	(setq ent (subst pt1 (assoc 10 ent) ent))
	(setq ent (subst pt2 (assoc 11 ent) ent))
	(entmod ent)
  )
	 
  (princ "\nSelect Lines & Polylines to reverse direction of:   ")
  (setq ss (ssget '((0 . "POLYLINE,LWPOLYLINE,LINE"))))
  (setvar "CMDECHO" 0)
  (command "._UNDO" "_BEgin")
  (if ss
	(progn
	  (setq count 0 lwp 0)
	  (while (> (sslength ss) count)
		(setq ent (ENTGET (ssname ss count))
				  obj (vlax-ename->vla-object (ssname ss count))
				  oname (vlax-get-property obj 'ObjectName)
		)
		(cond
		  ((= oname "AcDb3dPolyline")(setq lwp(+ 1 lwp)))
		  ((= (cdadr ent) "LWPOLYLINE")(revlwpl))
		  ((= (cdadr ent) "POLYLINE")
			(progn
			  (setq sss (ssadd (ssname ss count)))
			  (vl-cmdf "convertpoly" "Light" sss "")
			  (setq ent (ENTGET (ssname sss 0)))
			  (revlwpl)
			)
		  )
		  ((= (cdadr ent) "LINE")(revln))
		)
		(setq count (+ count 1))
	  )
	)
  )
  (command "._UNDO" "_End")
  (if(> lwp 0)
	(if(> lwp 1)
	  (princ(strcat "\nCould not reverse " (itoa lwp) " 3dPolylines."))
	  (princ"\nCould not reverse the 3dPolyline.")
	)
  )
  (princ)
)
