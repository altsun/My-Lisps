(defun c:+()  ;;; cong
	 (prompt "\nChon text de cong:")
	 (setq ss (ssget '((0 . "TEXT")))
	       tong 0)
	 (while (and ss (> (sslength ss) 0))
	   (setq tong (+ tong (atof (cdr (assoc 1 (entget (setq ent (ssname ss 0))))))))
	   (ssdel ent ss))
(setq s1 (entget (car (entsel "Chon Text ghi ket qua: "))))
(setq otext (assoc 1 s1))
(setq ot (cdr otext))
   (setq ot (read ot))
   (setq nt (cons 1 (strcat (rtos tong 2 2))))
   (entmod (subst nt otext s1))
(command "luprec" "2")
(setq s1 (ssget))
(command"chprop" "p" "" "c" 1 "")
(command "_.UNDO" "_END")
  (princ)
	 (princ tong))
