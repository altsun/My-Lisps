(defun c:V2T (/ sst)
  (setq	tapsua (list
		 (cons "®" "ñ")
		 (cons "§" "Ñ")
		 (cons "µ" "aø")
		 (cons "¸" "aù")
		 (cons "¶" "aû")
		 (cons "·" "aõ")
		 (cons "¹" "aï")
		 (cons "©" "aâ")
		 (cons "¢" "AÂ")
		 (cons "Ç" "aà")
		 (cons "Ê" "aá")
		 (cons "È" "aå")
		 (cons "É" "aã")
		 (cons "Ë" "aä")
		 (cons "¨" "aê")
		 (cons "¡" "AÊ")
		 (cons "»" "aè")
		 (cons "¾" "aé")
		 (cons "¼" "aú")
		 (cons "½" "aü")
		 (cons "Æ" "aë")
		 (cons "Ì" "eø")
		 (cons "Ð" "eù")
		 (cons "Î" "eû")
		 (cons "Ï" "eõ")
		 (cons "Ñ" "eï")
		 (cons "ª" "eâ")
		 (cons "£" "EÂ")
		 (cons "Ò" "eà")
		 (cons "Õ" "eá")
		 (cons "Ó" "eå")
		 (cons "Ô" "eã")
		 (cons "Ö" "eä")
		 (cons "×" "ì")
		 (cons "Ý" "í")
		 (cons "Ø" "æ")
		 (cons "Ü" "ó")
		 (cons "Þ" "ò")
		 (cons "ß" "oø")
		 (cons "ã" "où")
		 (cons "á" "oû")
		 (cons "â" "oõ")
		 (cons "ä" "oï")
		 (cons "«" "oâ")
		 (cons "¤" "OÂ")
		 (cons "å" "oà")
		 (cons "è" "oá")
		 (cons "æ" "oå")
		 (cons "ç" "oã")
		 (cons "é" "oä")
		 (cons "¬" "ô")
		 (cons "¥" "Ô")
		 (cons "ê" "ôø")
		 (cons "í" "ôù")
		 (cons "ë" "ôû")
		 (cons "ì" "ôõ")
		 (cons "î" "ôï")
		 (cons "ï" "uø")
		 (cons "ó" "uù")
		 (cons "ñ" "uû")
		 (cons "ò" "uõ")
		 (cons "ô" "uï")
		 (cons "­" "ö")
		 (cons "¦" "Ö")
		 (cons "õ" "öø")
		 (cons "ø" "öù")
		 (cons "ö" "öû")
		 (cons "÷" "öõ")
		 (cons "ù" "öï")
		 (cons "ú" "yø")
		 (cons "ý" "yù")
		 (cons "û" "yû")
		 (cons "ü" "yõ")
		 (cons "þ" "î")
	       )
	tapsua (mapcar '(lambda	(x)
			  (cons (cdr x) (car x))
			)
		       tapsua
	       )

  )
  (defun cf (stsua)
    (defun pos (sub st / l1 l2 index)
      (setq index 1
	    l1	  (strlen sub)
	    l2	  (strlen st)
      )
      (while
	(and (<= (+ index l1 -1) l2) (/= sub (substr st index l1)))
	 (setq index (1+ index))
      )
      (if (= sub (substr st index l1))
	index
	nil
      )
    )

    (setq stdich stsua
	  stht stdich)
    (foreach pt	tapsua
      (setq
	cansua	(car pt)
	suabang	(cdr pt)
      )
      (while (wcmatch stht (strcat "*" cansua "*"))
	(setq
	  vitri	 (pos cansua stdich)
	  stdich (strcat (substr stdich 1 (1- vitri))
			 suabang
			 (substr stdich (+ vitri (strlen cansua)))
		 )
	  vitri	 (pos cansua stht)
	  stht   (strcat (substr stht 1 (1- vitri))			 
			 (substr stht (+ vitri (strlen cansua)))
		 )
	)
      )
    )
    stdich
  )
  (defun VNI2TCVNone
		     (ent / daichuoi index stdich chuht CHUSUA)
    (setq
      tt     (entget ent)
      old    (assoc 1 tt)
      stsua  (cdr old)
      stdich (cf stsua)
      tt     (subst (cons 1 stdich) old tt)
    )
    (entmod tt)
    (entupd ent)
  )
  (defun sudung	(ham ss / sodt index entdt soapp)
    (setq sodt	(cond
		  (ss (sslength ss))
		  (t 0)
		)
	  soapp	0
	  index	0
    )
    (repeat sodt
      (setq entdt (ssname ss index)
	    index (1+ index)
      )
      (if (ham entdt)
	(setq soapp (1+ soapp))
      )
    )
    soapp
  )
  (princ "\nConvert text from VNI to ">TCVN3 - © CADViet.com")
  (setq sst (setq ss (ssget '((0 . "TEXT")))))
  (sudung VNI2TCVNone sst)
  (princ)
)
(princ
  "\nConvert text from VNI to ">TCVN3 - free lisp from www.cadviet.com"
)
(princ "\ntype V2T to start!")
(princ)
