(defun c:CUT (/ oldlayer oldos 1st_pt 2nd_pt 3rd_pt opwidth opening_ang brk_pt1 brk_pt2 brk_pt3 brk_pt4)
(setvar "cmdecho" 0)
(setq oldlayer (getvar "clayer"))
(setq oldos (getvar "osmode"))
(command ".undo" "begin")
   (setvar "osmode" 512)
   (setq 1st_pt (getpoint "\nPick point along wall..."))
   (setvar "osmode" 128)
   (setq 3rd_pt (getpoint 1st_pt "\nPick point perpendicular to other side of wall..."))
   (setvar "osmode" 512)
   (setq 2nd_pt (getpoint 1st_pt "\nPick point along same side of wall for direction and opening width..."))
   (setvar "osmode" 0)
   (setq getlay (nentselp 1st_pt))
   (setq lay (cdr (assoc 8 (entget (car getlay)))))
   (command ".layer" "set" lay "")  
   (setq opwidth (distance 1st_pt 2nd_pt))
   (setq opening_ang (angle 1st_pt 2nd_pt))
   (setq brk_pt1 1st_pt)
   (setq brk_pt2 (polar 1st_pt opening_ang opwidth))
   (setq brk_pt3 3rd_pt)
   (setq brk_pt4 (polar 3rd_pt opening_ang opwidth))
;--------- Break Wall ---------------
   (command "_break" brk_pt1 brk_pt2)
   (command "_break" brk_pt3 brk_pt4)
;--------- Cap Wall ---------------
   (command "_line" brk_pt1 brk_pt3 "")
   (command "_line" brk_pt2 brk_pt4 "")
(setvar "clayer" oldlayer)
(command ".undo" "end")
(setvar "osmode" oldos)
(setvar "cmdecho" 1)
(princ "\nDone!")
(princ)
)
