(defun c:PB (/ e l mp p1 p2)
  ;; RJP » 2018-12-17
  ;; Draws a pipe continuation based off of 2 picked points
  (cond	((and (setq p1 (getpoint "\nSelect first point: "))
	      (setq p2 (getpoint p1 "\nSelect second point: "))
	 )
	 (setq p1 (trans p1 1 0))
	 (setq p2 (trans p2 1 0))
	 (setq mp (polar p1 (angle p1 p2) (/ (distance p1 p2) 2.)))
	 (and (setq l (vl-some '(lambda (x) (nentselp x)) (list p1 p2)))
	      (setq l (cdr (assoc 8 (entget (car l)))))
	 )
	 (setq e (entmakex (list '(0 . "LWPOLYLINE")
				 '(100 . "AcDbEntity")
				 (cons 8
				       (if l
					 l
					 (getvar 'clayer)
				       )
				 )
				 '(100 . "AcDbPolyline")
				 '(90 . 4)
				 '(70 . 0)
				 (cons 10 p1)
				 '(42 . -0.5)
				 (cons 10 mp)
				 '(42 . 0.5)
				 (cons 10 p2)
				 '(42 . 0.5)
				 (cons 10 mp)
			   )
		 )
	 )
	 (while	(getpoint "\nPick a point to flip pipe end or enter to accept: ")
	   (entmod (mapcar '(lambda (x)
			      (cond ((and (= 42 (car x)) (/= 0 (cdr x))) (cons 42 (- (cdr x))))
				    (x)
			      )
			    )
			   (entget e)
		   )
	   )
	 )
	)
  )
  (princ)
)
