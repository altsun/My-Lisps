;; free lisp from cadviet.com
;;; this lisp was downloaded from http://www.cadviet.com/forum/topic/13203-viet-lisp-theo-yeu-cau-phan-2/page-36
;;;CHUONG TRINH VE THANG CAP DIEN - CAP TRUNKING;;;Written by THIEP 01/2010  www.cadviet.com;;;require install express tool
(defun off (OBJ flag)  (car (vlax-safearray->list	 (variant-value (vla-offset OBJ flag))       )  ))
(defun line (Model p1 p2)  (vla-AddLine    Model    (vlax-3d-point p1)    (vlax-3d-point p2)  ))(vl-load-com)
(defun C:thangcap (/ ActDoc *Model* *layer* enlay lay p1 p2 p3 Lpo ent		     obj Lcur flag obj1 obj2 obj3 obj4 lst1 lst2 n N0 l1 ok)  (setq	ActDoc	 (vla-get-ActiveDocument (vlax-get-acad-object))	*Model*	 (vla-get-ModelSpace ActDoc)	*layer*	(vla-get-Layers ActDoc)  )  (vla-StartUndoMark ActDoc)  (setq oldcmdo (getvar "cmdecho"))  (setq oldos (getvar "osmode"))  (setq oldlay (getvar "clayer"))  (if (not (setq enlay (tblobjname "layer" "E-AUXL")))      (setq lay (vla-add *layer* "E-AUXL"))    (progn      (setq lay (vlax-ename->vla-object enlay))      (setq lay (vla-add *layer* "E-AUXL"))    )  )  (setvar "cmdecho" 0)  (setvar "osmode" 0)  (setq	d0 (cond (d0)		 (500)	   )  )  (setq oldd0 d0)  (setq	d0 (getreal (strcat "\nDuong kinh thang (L) <"			    (rtos oldd0 2 0)			    "> : "		    )	   )  )  (if (null d0)    (setq d0 oldd0)  )  (setq	N0 (cond (N0)		 (300)	   )  )  (setq oldN0 N0)  (setq	N0 (getreal (strcat "\nBuoc thang (N) <"			    (rtos oldN0 2 0)			    "> : "		    )	   )  )  (if (null N0)    (setq N0 oldN0)  )  (setq	p1  (getpoint "\npick a point: ")	Lpo (list p1)  )  (while (setq p2 (getpoint p1 "\nPick a point continuous: "))    (setq Lpo (append Lpo (list p2)))    (GRDRAW p1 p2 7 0)    (setq p1 p2)  )  (ACET-LWPLINE-MAKE (list Lpo))  (setq	ent  (entlast)	OBJ  (vlax-ename->vla-object ent)	flag (/ d0 2)	Lcur (vla-get-Length OBJ)  )  (setq	obj1 (off OBJ (+ flag 30))	obj2 (off OBJ (- (+ flag 30)))	obj3 (off OBJ flag)	obj4 (off OBJ (- flag))  )  (setq	lst1 (ACET-GEOM-VERTEX-LIST (vlax-vla-object->ename obj1))	lst2 (ACET-GEOM-VERTEX-LIST (vlax-vla-object->ename obj2))	n    0  )  (repeat (length lst1)    (line *Model* (nth n lst1) (nth n lst2))    (setq n (1+ n))  )  (setq	n  (fix (/ Lcur N0))	l1 (/ N0 2))  (setvar "clayer" "E-AUXL")  (repeat n    (setq p1 (vlax-curve-getPointAtDist ent l1)	  p2 (vlax-curve-getClosestPointTo obj3 p1)	  p3 (vlax-curve-getClosestPointTo obj4 p1)    )    (off (line *Model* p2 p3) 30)     (setq l1 (+ l1 N0))  )  (vla-delete OBJ)  (vla-put-Comments    (vla-get-SummaryInfo      ActDoc      )    (setq ok "Thank you for use thangcap.lsp! THIEP 0918841230")  )  (vla-Regen ActDoc acActiveViewport)  (vla-EndUndoMark ActDoc)  (setvar "cmdecho" oldcmdo)  (setvar "osmode" oldos)  (setvar "clayer" oldlay)  (princ ok))
