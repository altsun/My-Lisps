;;CTK;;;;;;;;;;;;;;;;;;;;;;;;;;;;;;;;;;;;
(defun c:itk() (command "Import_CTK"))
(defun c:tkx() (command "thong_ke_excel"))
(defun c:tkm() (command "hieu_chinh_thong_ke"))
(defun c:tht() (command "tonghopthep"))
(defun c:CTI() (command "chenthongke"))
(defun c:CTM() (command "hieuchinhthongke2"))

;;LAT;;;;;;;;;;;;;;;;;;;;;;;;;;
(defun c:at() (command "velanhto"))
(defun c:atk() (command "thongkelanhto"))

;;Plotter ;;;;;;;;;;;;;;;;;;;;;
(defun c:kp() (command "kcsplotter"))
(defun c:kl() (command "vevungin"))
(defun c:kpp() (command "kcsplotterpro"))

;;SFD;;;;;;;;;;;;;;;;;;;;;;;;;;;;;;;;
(defun c:sfd() (command "vemongbang"))

;;STK;;;;;;;;;;;;;;;;;;;;;;;;;;;;;;;;;
(defun c:STI() (command "chenthongkestk"))
(defun c:STM() (command "hieuchinhstk"))
(defun c:IST() (command "Import_STK"))
(defun c:TST() (command "tonghopthepstk"))

;;PFDe;;;;;;;;;;;;;;;;;;;;;;;;;;;;;;;;
(defun c:pfd() (command "vemongcoc"))

;;PTSection;;;;;;;;;;;;;;;;;;;;;;;;;;;
(defun c:pts() (command "matcatsanust"))
(defun c:cap() (command "hotrosafevecap"))

;;Quickdraw ;;;;;;;;;;;;;;;;;;;;;;;;;;;
(defun c:sd() (command "suadim"))
(defun c:tkt() (command "thongketext"))
(defun c:dp() (command "vedamphu"))
(defun c:vc() (command "vecottrenmatbang"))
(defun c:tkd() (command "thongkedaitheotext"))
(defun c:dad() (command "doitextthepdai"))
(defun c:lkt() (command "lokythuat"))
(defun c:dg() (command "veluoicot"))
(defun c:ktv() (command "xuatktv"))
(defun c:vb() (command "vevachbe"))
(defun c:vd() (command "offset2ben"))
(defun c:vd2() (command "offset2ben2"))
(defun c:kcs() (command "kcspanel"))

;;RCB;;;;;;;;;;;;;;;;;;;;;;;;;;;;;;;;;;;;;
(defun c:rcb() (command "rcbdraw"))
(defun c:dtmc() (command "doitenmatcat"))
(defun c:ib() (command "importbeam"))
(defun c:bb() (command "breakbeam"))
(defun c:bbi() (command "breakbeammirror"))
(defun c:bx() (command "break_line_x"))
(defun c:by() (command "break_line_y"))
(defun c:byy() (command "break_line_y2"))
(defun c:gb() (command "getbeamdim"))

;;RCCd;;;;;;;;;;;;;;;;;;;;;;;;;;;;;;;;;;;;;
(defun c:rcc() (command "rccdraw"))

;;RCS ;;;;;;;;;;;;;;;;;;;;;;;;;;;;;;;;;;;;;
(defun c:vts() (command "vethepsan"))
(defun c:vmc() (command "vematcatsan"))
(defun c:vds() (command "danhsothepsan"))
(defun c:vcl() (command "canlesothep"))
(defun c:vhc() (command "hieuchinhthepsan"))
(defun c:vcf() (command "rcsconfig"))
(defun c:vtg() (command "thepgiathepmu"))
(defun c:vtg2() (command "thepgiathepmu2"))

;;KCS VCT ;;;;;;;;;;;;;;;;;;;;;;;;;;;;;;;;;
(defun c:vct() (command "vematcat"))

;;KCS PLOTER ;;;;;;;;;;;;;;;;;;;;;;;;;;;;;;;;;
(defun c:tbv() (command "kcschuyenlayertbv"))
(defun c:sbv() (command "kcschuyenlayersbv"))
(defun c:tck() (command "kcschuyenlayertck"))
(defun c:te() (command "thongkecaukien"))
